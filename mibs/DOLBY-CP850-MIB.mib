DOLBY-CP850-MIB


DEFINITIONS ::= BEGIN


IMPORTS
         MODULE-IDENTITY, OBJECT-TYPE, NOTIFICATION-TYPE
                FROM SNMPv2-SMI

         MODULE-COMPLIANCE, OBJECT-GROUP, NOTIFICATION-GROUP
                FROM SNMPv2-CONF

         TruthValue
                FROM SNMPv2-TC

         dolbyModules
                FROM DOLBY-SMI

         cp850Reg
                FROM DOLBY-GLOBAL-REG

         cinemaProcessors
                FROM DOLBY-PRODUCTS-MIB;


dolbyCP850MIBModule MODULE-IDENTITY

                LAST-UPDATED
                                "201605260000Z"

                ORGANIZATION
                                "Dolby Laboratories Inc."

                CONTACT-INFO
                                "Ethan Grossman
                                 email: eagros@dolby.com"

                DESCRIPTION
                                "The Dolby Laboratories CP850
                                 product MIB module"

                REVISION
                                "201605260000Z"

                DESCRIPTION     "MIB for the CP850 Cinema Processor. Output strings are now compatible with CP850 Web Services strings. Now includes Security Alert."

		::= {dolbyModules 11}


--
-- Local object definitions
--

cp850Root           OBJECT IDENTIFIER       ::= { cinemaProcessors 3 }
cp850Info           OBJECT IDENTIFIER       ::= { cp850Root 1 }
cp850Status         OBJECT IDENTIFIER       ::= { cp850Root 2 }

--
-- Info
--

cp850Cat1600SerialNumber	OBJECT-TYPE
			SYNTAX		OCTET STRING (SIZE (0..64))
			MAX-ACCESS	read-only
			STATUS		 current
			DESCRIPTION
				"The serial number of the CP850's CAT1600 I/O board."

			::=	{ cp850Info 1 }

cp850SoftwareVersion	OBJECT-TYPE
			SYNTAX		OCTET STRING (SIZE (0..32))
			MAX-ACCESS	read-only
			STATUS		 current
			DESCRIPTION
				"The Software Version running on the CP850."

			::=	{ cp850Info 2 }

cp850FirmwareVersion	OBJECT-TYPE
			SYNTAX		OCTET STRING (SIZE (0..32))
			MAX-ACCESS	read-only
			STATUS		 current
			DESCRIPTION
				"The Firmware Version running on the CP850."
			::=	{ cp850Info 3 }

--
-- Status
--

cp850FaderLevel	OBJECT-TYPE
			SYNTAX		OCTET STRING (SIZE (0..16))
			MAX-ACCESS	read-only
			STATUS		 current
			DESCRIPTION
				"The current setting of the Front Panel Fader. Values range from '0' to '100'"

			::=	{ cp850Status 1 }

cp850MuteStatus	OBJECT-TYPE
			SYNTAX		OCTET STRING (SIZE (0..16))
			MAX-ACCESS	read-only
			STATUS		 current
			DESCRIPTION
				"The current setting of the Front Panel Mute button. Value is either 'True' (muted) or 'False' (not muted)"

			::=	{ cp850Status 2 }

cp850DigitalOutputMode	OBJECT-TYPE
			SYNTAX		OCTET STRING (SIZE (0..16))
			MAX-ACCESS	read-only
			STATUS		 current
			DESCRIPTION
				"The currently configured Dolby Atmos Connect output mode. Value is either 'AES67' or 'BLULINK'"

			::=	{ cp850Status 3 }

cp850BitstreamFormat	OBJECT-TYPE
			SYNTAX		OCTET STRING (SIZE (0..32))
			MAX-ACCESS	read-only
			STATUS		 current
			DESCRIPTION
				"The current format of the audio input, value can be one of: 
                    'dolbyAtmos'
                    'dolbyAtmosRevertedToPCM'
                    'pcm' 
                    'dolbyDigital' 
                    'dolbyDigitalPlus' 
                    'dolbyE' 
                    'dolbyTrueHD' 
                    'dolbyMAT'
                    'n/a'" 

			::=	{ cp850Status 4 }

cp850AESSyncState	OBJECT-TYPE
			SYNTAX		OCTET STRING (SIZE (0..16))
			MAX-ACCESS	read-only
			STATUS		 current
			DESCRIPTION
				"AES 16 channel (8 pairs) input sync state. Value is a set of 8 digits, 
				     each of which can be 1 (pair locked) or 0 (pair unlocked), 
				     for example '11111110' says all pairs are locked except pair 15/16."

			::=	{ cp850Status 5 }

cp850Enablements	OBJECT-TYPE
			SYNTAX		OCTET STRING (SIZE (0..64))
			MAX-ACCESS	read-only
			STATUS		 current
			DESCRIPTION
				"Valid installed enablement codes. Value is a string like '1 4 6' to say that enablements with codes 1,4,6 are installed, others are not."

			::=	{ cp850Status 6 }

cp850DecodeMode	OBJECT-TYPE
			SYNTAX		OCTET STRING (SIZE (0..16))
			MAX-ACCESS	read-only
			STATUS		 current
			DESCRIPTION
				"Channel layout of audio. Values can be one of:
                '1+1' 
                '1.0' 
                '2.0' 
                '3.0' 
                '2.1' 
                '3.1' 
                '4.1' 
                '5.1' 
                '7.1'
                'n/a'"

			::=	{ cp850Status 7 }

cp850InputSelection	OBJECT-TYPE
			SYNTAX		OCTET STRING (SIZE (0..64))
			MAX-ACCESS	read-only
			STATUS		 current
			DESCRIPTION
				"Selected input of the current macro. Values can be one of: 
                'none' 
                '16ch. AES Digital + Dolby Atmos (A)' 
                'AES-3id BNC (C)' 
                'AES-3id BNC (B)' 
                'S/PDIF Optical (D)' 
                'S/PDIF RCA (E)' 
                'HDMI (IN 1)' 
                'HDMI (IN 2)' 
                'Non-sync' 
                'P.A. Microphone (Mic 1)' 
                'RTA Microphone (Mic 2)' 
                '16ch. AES Digital PCM-only (A)'"

			::=	{ cp850Status 8 }

cp850AudioDelay	OBJECT-TYPE
			SYNTAX		OCTET STRING (SIZE (0..16))
			MAX-ACCESS	read-only
			STATUS		 current
			DESCRIPTION
				"Global delay setting of the current macro in milliseconds. Values can be between '20' and '1000'"

			::=	{ cp850Status 9 }


cp850MeterLevels	OBJECT-TYPE
 			SYNTAX		OCTET STRING (SIZE (0..32))
			MAX-ACCESS	read-only
			STATUS		current
			DESCRIPTION
			"Meter readings as a set of values in the order 'L R C LFE Lss Rss Lrs Rrs Lts Rts'.
			 Two character value per channel with a space between each channel, updated about 20 times/second.
		         Range is between 00 and 60, in dB peak, where 60dB is 0dBFS. Example: '10 55 00 50 10 01 37 58 00 00'"

 			::=	{ cp850Status 10 }

cp850SecurityAlert	OBJECT-TYPE
			SYNTAX		OCTET STRING (SIZE (0..256))
			MAX-ACCESS	read-only
			STATUS		 current
			DESCRIPTION
				"Normally set to 'No security alert'. If a security alert is detected, this string will 
				be updated to 'Security chip has been tampered' followed by a statement of the cause(s)
				of the alert. When this alert is activated, secure content playback is disabled - contact Dolby support."

			::=	{ cp850Status 11 }

cp850BitstreamEncrypted	OBJECT-TYPE
			SYNTAX		OCTET STRING (SIZE (0..16))
			MAX-ACCESS	read-only
			STATUS		 current
			DESCRIPTION
				"The encrypted state of the bitstream, value can be one of:
                                'yes' -> implies atmos bitstream is encrypted
                                'no'  -> implies atmos bitstream is not encrypted
                                'n/a' -> encrypted state is not applicable to current format"

			::=	{ cp850Status 12 }

cp850Cat1610LowBattery	OBJECT-TYPE
			SYNTAX		TruthValue
			MAX-ACCESS	read-only
			STATUS		 current
			DESCRIPTION
				"Whether or not there CAT1610 battery voltage is low. 
                                 true(1) indicates battery voltage is below threshold; 
                                false(2) indicates battery voltage is above threshold"

			::=	{ cp850Status 13 }


--
-- Notifications (none)
--


---
--- Conformance statements
---

cp850Conformances	OBJECT IDENTIFIER     ::= { cp850Reg 1 }

cp850Groups		OBJECT IDENTIFIER     ::= { cp850Conformances 1 }

cp850InfoGroup  OBJECT-GROUP
			OBJECTS { cp850Cat1600SerialNumber,
                                cp850SoftwareVersion,
                                cp850FirmwareVersion
                        }
			STATUS	current
			DESCRIPTION
				"Informational objects required for
				 the basic implementation of the CP850 MIB."

			::= { cp850Groups 1 }


cp850StatusGroup  OBJECT-GROUP
			OBJECTS	{ cp850FaderLevel,
                cp850MuteStatus,
                cp850DigitalOutputMode,
                cp850BitstreamFormat,
                cp850AESSyncState,
                cp850Enablements,
                cp850DecodeMode,
                cp850InputSelection,
                cp850AudioDelay,
                cp850MeterLevels,
                cp850SecurityAlert,
                cp850BitstreamEncrypted,
                cp850Cat1610LowBattery
				}
			STATUS	current
			DESCRIPTION
				"Status objects required for the basic
				 implementation of the CP850 MIB."

			::= { cp850Groups 2 }


cp850Compliances	OBJECT IDENTIFIER     ::= { cp850Conformances 2 }

cp850BasicCompl		MODULE-COMPLIANCE
			STATUS	current
			DESCRIPTION
				"The basic implementation requirements 
				for the CP850 MIB."
			MODULE
				MANDATORY-GROUPS { cp850InfoGroup,
						   cp850StatusGroup
						 }

			::= { cp850Compliances 1 }


END
