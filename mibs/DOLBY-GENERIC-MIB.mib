DOLBY-GENERIC-MIB

DEFINITIONS ::= BEGIN

IMPORTS
	MODULE-IDENTITY,OBJECT-IDENTITY

		FROM SNMPv2-SMI

	dolbyGeneric,dolbyModules

		FROM DOLBY-SMI;


dolbyGenericModule	MODULE-IDENTITY

	LAST-UPDATED	"202001150000Z"

	ORGANIZATION	"Dolby Laboratories Inc."

	CONTACT-INFO	"Steve Oddo
			 email: sjo@dolby.com"

	DESCRIPTION	"The Dolby Laboratories generic product module
			 Copyright 2020 Dolby Laboratories Inc"

	REVISION	"202001150000Z"
	DESCRIPTION	"Added generic Cinema Components - preliminary"

        ::= { dolbyModules 14 }
        
--
-- Top-level tree for Dolby product-generic characteristics
--


--
-- Product divisions
--

dolbyProGeneric      OBJECT IDENTIFIER ::= { dolbyGeneric 1 }
dolbyConsumerGeneric OBJECT IDENTIFIER ::= { dolbyGeneric 2 }
dolbyVoiceGeneric    OBJECT IDENTIFIER ::= { dolbyGeneric 3 }

--
-- Other product divisions ...
--


--
-- Product families
--

proCinemaGeneric    OBJECT IDENTIFIER ::= { dolbyProGeneric 1 }


--
-- Other product families ...
--


--
-- Individual products
--

--
-- Cinema product lines
--

cinemaProcessorsGeneric	        OBJECT-IDENTITY
	STATUS	current
	DESCRIPTION	"Cinema processor objects and events"
	::= { proCinemaGeneric 1 }

--
-- Other product lines ...
--


END
